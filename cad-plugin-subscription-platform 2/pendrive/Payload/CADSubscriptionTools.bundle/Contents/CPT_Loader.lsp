;;; CAD Subscription Tools - AutoCAD loader
;;; This file is loaded by AutoCAD through PackageContents.xml.

(vl-load-com)

(setq CPT:APP-NAME "CAD Subscription Tools")
(setq CPT:ROOT (vl-filename-directory *load-truename*))
(setq CPT:TOOLS-DIR (strcat CPT:ROOT "\\Tools"))
(setq CPT:LICENSE-DIR (strcat (getenv "APPDATA") "\\CADSubscriptionTools\\License"))
(setq CPT:LICENSE-FILE (strcat CPT:LICENSE-DIR "\\license.lsp"))

(defun CPT:ensure-dir (path)
  (if (and path (not (vl-file-directory-p path)))
    (vl-mkdir path)
  )
)

(defun CPT:join (base file)
  (strcat base "\\" file)
)

(defun CPT:license-active-p (/)
  (if (findfile CPT:LICENSE-FILE)
    (progn
      (load CPT:LICENSE-FILE)
      (and (boundp 'CPT_LICENSE_STATUS)
           (= (strcase CPT_LICENSE_STATUS) "ACTIVE"))
    )
    nil
  )
)

(defun CPT:load-one-tool (file / full-path result)
  (setq full-path (CPT:join CPT:TOOLS-DIR file))
  (if (findfile full-path)
    (progn
      (setq result (vl-catch-all-apply 'load (list full-path)))
      (if (vl-catch-all-error-p result)
        (princ (strcat "\n[CPT] Could not load " file ": " (vl-catch-all-error-message result)))
        (princ (strcat "\n[CPT] Loaded " file))
      )
    )
    (princ (strcat "\n[CPT] Missing tool file: " file))
  )
)

(defun CPT:load-approved-tools (/ manifest)
  (setq manifest (CPT:join CPT:TOOLS-DIR "tools-manifest.lsp"))
  (if (findfile manifest)
    (progn
      (load manifest)
      (if (and (boundp 'CPT_TOOL_FILES) CPT_TOOL_FILES)
        (foreach tool CPT_TOOL_FILES (CPT:load-one-tool tool))
        (princ "\n[CPT] Manifest exists, but CPT_TOOL_FILES is empty.")
      )
    )
    (princ "\n[CPT] tools-manifest.lsp was not found.")
  )
)

(defun CPT:bootstrap (/)
  (if (CPT:license-active-p)
    (progn
      (CPT:load-approved-tools)
      (princ "\n[CPT] CAD Subscription Tools is ready. Type CPTABOUT for details.")
    )
    (princ "\n[CPT] License inactive. Type CPTACTIVATE to activate on this computer.")
  )
  (princ)
)

(defun c:CPTACTIVATE (/ key f)
  (CPT:ensure-dir CPT:LICENSE-DIR)
  (setq key (getstring T "\nEnter customer license key: "))
  (if (> (strlen key) 3)
    (progn
      (setq f (open CPT:LICENSE-FILE "w"))
      (write-line ";;; Local activation file generated by CPTACTIVATE." f)
      (write-line "(setq CPT_LICENSE_STATUS \"ACTIVE\")" f)
      (write-line (strcat "(setq CPT_LICENSE_KEY \"" key "\")") f)
      (write-line (strcat "(setq CPT_LICENSE_MACHINE \"" (getenv "COMPUTERNAME") "\")") f)
      (close f)
      (princ "\n[CPT] License saved. Type CPTRELOAD or restart AutoCAD.")
    )
    (princ "\n[CPT] Activation cancelled. Enter a valid key.")
  )
  (princ)
)

(defun c:CPTRELOAD (/)
  (CPT:bootstrap)
  (princ)
)

(defun c:CPTABOUT (/)
  (princ "\nCAD Subscription Tools")
  (princ "\nCommands: CPTACTIVATE, CPTRELOAD, CPTABOUT")
  (if (CPT:license-active-p)
    (princ "\nLicense: ACTIVE")
    (princ "\nLicense: INACTIVE")
  )
  (princ)
)

(CPT:bootstrap)
(princ)
